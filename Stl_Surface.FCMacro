# -*- coding: utf-8 -*-
# FreeCAD CAM Macro - STL 2.5D Engraving V1
#
# V1:
# - Select one STL/Mesh object
# - Use an existing CAM Job
# - Select a Tool Controller from the Job
# - Generate a simple parallel / zig-zag raster
# - Use OpenCAMLib PathDropCutter for Z projection
# - Create a Custom Operation inside the Job
#
# No independent G-code export.
# Job Clearance/Safe heights are used; they are NOT duplicated here.

import FreeCAD
import FreeCADGui
import Path
import Path.Op.Custom as custom
import Path.Op.Gui.Base as GuiBase
import PathScripts.PathUtils as PathUtils
from Path.Op.Gui.Base import CommandResources, TaskPanelPage
from Path.Base import FeedRate
from PySide6 import QtWidgets, QtCore
from opencamlib import ocl


# ---------------------------------------------------------------------------
# Helpers
# ---------------------------------------------------------------------------

def get_selected_mesh():
    sel = FreeCADGui.Selection.getSelection()
    if len(sel) != 1:
        QtWidgets.QMessageBox.critical(
            None,
            "STL 2.5D Engraving",
            "Select exactly ONE STL/Mesh object before starting the macro."
        )
        return None

    obj = sel[0]

    if not obj.TypeId.startswith("Mesh"):
        QtWidgets.QMessageBox.critical(
            None,
            "STL 2.5D Engraving",
            "The selected object must be a Mesh/STL object."
        )
        return None

    return obj


def find_job(doc):
    job = doc.getObject("Job")
    if job:
        return job

    for obj in doc.Objects:
        try:
            if obj.Name == "Job" or obj.Label == "Job":
                return obj
        except Exception:
            pass

    QtWidgets.QMessageBox.critical(
        None,
        "STL 2.5D Engraving",
        "No CAM Job was found in the active document."
    )
    return None


def get_tool_controllers(job):
    result = []

    try:
        if job and job.Tools and job.Tools.Group:
            for obj in job.Tools.Group:
                result.append(obj)
    except Exception as e:
        FreeCAD.Console.PrintError(
            "Error reading Job Tools: %s\\n" % str(e)
        )

    return result


def make_ocl_surface(mesh_obj):
    surface = ocl.STLSurf()

    for facet in mesh_obj.Mesh.Facets:
        p1, p2, p3 = facet.Points

        surface.addTriangle(
            ocl.Triangle(
                ocl.Point(*p1),
                ocl.Point(*p2),
                ocl.Point(*p3),
            )
        )

    return surface


def make_ocl_cutter(tool):
    shape_id = getattr(tool, "ShapeID", "")

    if shape_id == "endmill":
        return ocl.CylCutter(
            tool.Diameter.Value,
            tool.Length.Value
        )

    if shape_id == "ballend":
        return ocl.BallCutter(
            tool.Diameter.Value,
            tool.Length.Value
        )

    if shape_id == "bullnose":
        return ocl.BullCutter(
            tool.Diameter.Value,
            tool.CornerRadius.Value,
            tool.CuttingEdgeHeight.Value
        )

    if shape_id == "v-bit":
        return ocl.ConeCutter(
            tool.Diameter.Value,
            tool.CuttingEdgeAngle.Value / 2.0,
            tool.CuttingEdgeHeight.Value
        )

    raise RuntimeError(
        "Unsupported OCL cutter type: " + str(shape_id)
    )


def remove_collinear(points, tol=1e-7):
    if len(points) < 3:
        return points

    result = [points[0]]

    for i in range(1, len(points) - 1):
        v1 = points[i] - result[-1]
        v2 = points[i + 1] - points[i]

        if v1.cross(v2).Length > tol:
            result.append(points[i])

    result.append(points[-1])
    return result


# ---------------------------------------------------------------------------
# Dialog
# ---------------------------------------------------------------------------

class EngravingDialog(QtWidgets.QDialog):

    def __init__(self, job, mesh_obj):
        super().__init__()

        self.job = job
        self.mesh_obj = mesh_obj
        self.setWindowTitle("STL 2.5D Engraving - V1")
        self.setMinimumWidth(430)

        layout = QtWidgets.QVBoxLayout(self)

        # Source
        source_box = QtWidgets.QGroupBox("Source")
        source_layout = QtWidgets.QFormLayout(source_box)

        self.source_label = QtWidgets.QLabel(mesh_obj.Label)
        source_layout.addRow("STL:", self.source_label)

        job_label = QtWidgets.QLabel(job.Label)
        source_layout.addRow("Job:", job_label)

        layout.addWidget(source_box)

        # Cutting
        cut_box = QtWidgets.QGroupBox("Cutting")
        cut_layout = QtWidgets.QFormLayout(cut_box)

        self.depth = QtWidgets.QDoubleSpinBox()
        self.depth.setRange(0.001, 1000.0)
        self.depth.setDecimals(3)
        self.depth.setValue(3.0)
        self.depth.setSuffix(" mm")

        self.stepdown = QtWidgets.QDoubleSpinBox()
        self.stepdown.setRange(0.0, 1000.0)
        self.stepdown.setDecimals(3)
        self.stepdown.setValue(0.5)
        self.stepdown.setSuffix(" mm")

        self.stepover = QtWidgets.QDoubleSpinBox()
        self.stepover.setRange(0.001, 1000.0)
        self.stepover.setDecimals(3)
        self.stepover.setValue(0.5)
        self.stepover.setSuffix(" mm")

        self.mode = QtWidgets.QComboBox()
        self.mode.addItem("Roughing", "roughing")
        self.mode.addItem("Finishing", "finishing")

        self.allowance_xy = QtWidgets.QDoubleSpinBox()
        self.allowance_xy.setRange(0.0, 1000.0)
        self.allowance_xy.setDecimals(3)
        self.allowance_xy.setValue(0.5)
        self.allowance_xy.setSuffix(" mm")

        self.allowance_z = QtWidgets.QDoubleSpinBox()
        self.allowance_z.setRange(0.0, 1000.0)
        self.allowance_z.setDecimals(3)
        self.allowance_z.setValue(0.2)
        self.allowance_z.setSuffix(" mm")

        self.margin = QtWidgets.QDoubleSpinBox()
        self.margin.setRange(0.0, 1000.0)
        self.margin.setDecimals(3)
        self.margin.setValue(0.0)
        self.margin.setSuffix(" mm")

        self.sampling = QtWidgets.QDoubleSpinBox()
        self.sampling.setRange(0.001, 100.0)
        self.sampling.setDecimals(3)
        self.sampling.setValue(0.10)
        self.sampling.setSuffix(" mm")

        cut_layout.addRow("Mode:", self.mode)
        cut_layout.addRow("Step Over:", self.stepover)
        cut_layout.addRow("Step Down:", self.stepdown)
        cut_layout.addRow("Allowance XY:", self.allowance_xy)
        cut_layout.addRow("Allowance Z:", self.allowance_z)
        cut_layout.addRow("Margin:", self.margin)
        cut_layout.addRow("Depth Limit:", self.depth)
        cut_layout.addRow("OCL Sampling:", self.sampling)


        layout.addWidget(cut_box)

        # Strategy
        strategy_box = QtWidgets.QGroupBox("Strategy")
        strategy_layout = QtWidgets.QFormLayout(strategy_box)

        self.direction = QtWidgets.QComboBox()
        self.direction.addItem("X", "X")
        self.direction.addItem("Y", "Y")

        self.pattern = QtWidgets.QComboBox()
        self.pattern.addItem("Zig-Zag", "zigzag")
        self.pattern.addItem("One Way", "oneway")

        strategy_layout.addRow("Direction:", self.direction)
        strategy_layout.addRow("Pattern:", self.pattern)

        layout.addWidget(strategy_box)

        # Buttons
        buttons = QtWidgets.QDialogButtonBox(
            QtWidgets.QDialogButtonBox.Ok |
            QtWidgets.QDialogButtonBox.Cancel
        )

        buttons.button(QtWidgets.QDialogButtonBox.Ok).setText("Calculate")
        buttons.accepted.connect(self.accept)
        buttons.rejected.connect(self.reject)

        layout.addWidget(buttons)

        self.mode.currentIndexChanged.connect(self.update_mode_ui)
        self.update_mode_ui()

    def update_mode_ui(self):
        roughing = self.mode.currentData() == "roughing"
        self.stepdown.setEnabled(roughing)
        self.allowance_xy.setEnabled(roughing)
        self.allowance_z.setEnabled(roughing)
        if not roughing:
            self.stepdown.setValue(0.0)
            self.allowance_xy.setValue(0.0)
            self.allowance_z.setValue(0.0)

    def values(self):
        return {
            "mode": self.mode.currentData(),
            "stepover": self.stepover.value(),
            "stepdown": self.stepdown.value(),
            "allowance_xy": self.allowance_xy.value(),
            "allowance_z": self.allowance_z.value(),
            "margin": self.margin.value(),
            "depth": self.depth.value(),
            "sampling": self.sampling.value(),
            "direction": self.direction.currentData(),
            "pattern": self.pattern.currentData(),
        }


# ---------------------------------------------------------------------------
# Custom operation
# ---------------------------------------------------------------------------

class EngravingProxy:

    def __init__(self, obj):
        obj.Proxy = self

    def execute(self, obj):
        # Path is generated directly by the macro.
        # Do not regenerate it here in V1.
        if hasattr(obj, "ViewObject") and obj.ViewObject:
            obj.ViewObject.Visibility = obj.Active

    def onChanged(self, obj, prop):
        if prop == "Active":
            if hasattr(obj, "ViewObject") and obj.ViewObject:
                obj.ViewObject.Visibility = obj.Active


def create_operation(job, params):
    name = "STL_2.5D_Engraving"

    op = custom.Create(name, parentJob=job)

    if not hasattr(op, "Proxy") or not isinstance(
        op.Proxy, custom.ObjectCustom
    ):
        custom.ObjectCustom(op)

    if FreeCAD.GuiUp:
        resources = CommandResources(
            name="STL 2.5D Engraving",
            objFactory=custom.Create,
            opPageClass=TaskPanelPage,
            pixmap="CAM_Custom",
            menuText="STL 2.5D Engraving",
            accelKey="",
            toolTip="OpenCAMLib STL 2.5D engraving operation",
        )

        op.ViewObject.Proxy = GuiBase.ViewProvider(
            op.ViewObject,
            resources
        )

    if not hasattr(op, "IsCustomOp"):
        op.addProperty(
            "App::PropertyBool",
            "IsCustomOp",
            "Path"
        )
    op.IsCustomOp = True

    if not hasattr(op, "STLSource"):
        op.addProperty(
            "App::PropertyLink",
            "STLSource",
            "Geometry",
            "STL/Mesh used for the engraving"
        )
    op.STLSource = params["mesh_obj"]

    if not hasattr(op, "MaximumDepth"):
        op.addProperty(
            "App::PropertyDistance",
            "MaximumDepth",
            "Parameters"
        )

    if not hasattr(op, "StepDown"):
        op.addProperty(
            "App::PropertyDistance",
            "StepDown",
            "Parameters"
        )

    if not hasattr(op, "StepOver"):
        op.addProperty(
            "App::PropertyDistance",
            "StepOver",
            "Parameters"
        )

    if not hasattr(op, "Sampling"):
        op.addProperty(
            "App::PropertyDistance",
            "Sampling",
            "Parameters"
        )

    if not hasattr(op, "Direction"):
        op.addProperty(
            "App::PropertyEnumeration",
            "Direction",
            "Parameters"
        )
        op.Direction = ["X", "Y"]

    if not hasattr(op, "Pattern"):
        op.addProperty(
            "App::PropertyEnumeration",
            "Pattern",
            "Parameters"
        )
        op.Pattern = ["Zig-Zag", "One Way"]

    for name, desc in [
        ("AllowanceXY", "Allowance XY"),
        ("AllowanceZ", "Allowance Z"),
        ("Margin", "Margin"),
    ]:
        if not hasattr(op, name):
            op.addProperty("App::PropertyDistance", name, "Parameters", desc)

    if not hasattr(op, "Mode"):
        op.addProperty("App::PropertyEnumeration", "Mode", "Parameters")
        op.Mode = ["Roughing", "Finishing"]

    op.Mode = "Roughing" if params["mode"] == "roughing" else "Finishing"
    op.MaximumDepth = params["depth"]
    op.StepDown = params["stepdown"]
    op.StepOver = params["stepover"]
    op.AllowanceXY = params["allowance_xy"]
    op.AllowanceZ = params["allowance_z"]
    op.Margin = params["margin"]
    op.Sampling = params["sampling"]
    op.Direction = params["direction"]
    op.Pattern = "Zig-Zag" if params["pattern"] == "zigzag" else "One Way"

    EngravingProxy(op)

    return op


# ---------------------------------------------------------------------------
# Toolpath generation
# ---------------------------------------------------------------------------

def generate_toolpath(mesh_obj, tool_controller, params, job, progress=None):
    doc = FreeCAD.ActiveDocument

    def update_progress(value, message):
        if progress is not None:
            progress.setValue(max(0, min(100, int(value))))
            progress.setLabelText(message)
            QtWidgets.QApplication.processEvents()

            if progress.wasCanceled():
                raise RuntimeError("Calculation cancelled by user")

    tool = tool_controller.Tool
    cutter = make_ocl_cutter(tool)
    surface = make_ocl_surface(mesh_obj)

    bb = mesh_obj.Mesh.BoundBox

    margin = params["margin"]
    allowance_xy = params["allowance_xy"]
    allowance_z = params["allowance_z"]

    # Margin extends the machining area. XY allowance does the opposite:
    # roughing must stay inside the final XY boundary so material remains
    # for the finishing operation.
    xmin = bb.XMin - margin + allowance_xy
    xmax = bb.XMax + margin - allowance_xy
    ymin = bb.YMin - margin + allowance_xy
    ymax = bb.YMax + margin - allowance_xy

    if xmin > xmax or ymin > ymax:
        raise RuntimeError(
            "Allowance XY is larger than the available STL area. "
            "Reduce Allowance XY or increase Margin."
        )
    zmax = bb.ZMax

    max_depth = params["depth"]
    stepdown = params["stepdown"]
    stepover = params["stepover"]
    sampling = params["sampling"]

    # Depth Limit is measured down from the STL top surface.
    # Depth Limit is measured down from the STL top surface.
    # Z allowance is material deliberately left for finishing. It applies
    # to EVERY roughing pass, not only the last one.
    target_z = zmax - max_depth
    final_z = target_z + allowance_z

    if params["mode"] == "finishing":
        # Finishing is a single pass. In the UI Allowance Z is disabled
        # and forced to zero, so this is normally exactly target_z.
        passes = [final_z]
    else:
        if stepdown <= 0:
            stepdown = max_depth
        passes = []
        z = zmax - stepdown
        # Intermediate roughing passes continue toward the final target.
        # The last pass stops at final_z, preserving the requested Z allowance.
        while z > final_z + 1e-9:
            passes.append(z)
            z -= stepdown
        if not passes or abs(passes[-1] - final_z) > 1e-9:
            passes.append(final_z)

    # Clearance comes from the Job.
    safe_z = 5.0

    try:
        safe_z = job.ClearanceHeight.Value
    except Exception:
        pass

    commands = []

    total_passes = len(passes)

    FreeCAD.Console.PrintMessage(
        "Depth target: %.3f mm | Z allowance: %.3f mm | Final pass: %.3f mm\n"
        % (target_z, allowance_z, final_z)
    )

    # Initial safe move.
    commands.append(Path.Command("G0", {"Z": safe_z}))

    # Build raster lines.
    direction = params["direction"]
    zigzag = params["pattern"] == "zigzag"

    if direction == "X":
        fixed_values = []
        y = ymin

        while y <= ymax + 1e-9:
            fixed_values.append(y)
            y += stepover

        if fixed_values[-1] < ymax - 1e-9:
            fixed_values.append(ymax)

        line_start = (xmin, fixed_values[0])
        commands.append(
            Path.Command(
                "G0",
                {"X": line_start[0], "Y": line_start[1]}
            )
        )

        total_lines = len(fixed_values)

        for pass_index, pass_z in enumerate(passes):
            first_line = True
            reverse = False

            for line_index, y in enumerate(fixed_values):
                progress_value = (
                    (pass_index * total_lines + line_index)
                    * 100.0
                    / max(1, total_passes * total_lines)
                )
                update_progress(
                    progress_value,
                    "Calculating... Pass %d/%d - Line %d/%d"
                    % (
                        pass_index + 1,
                        total_passes,
                        line_index + 1,
                        total_lines,
                    )
                )
                x1, x2 = xmin, xmax

                if zigzag and reverse:
                    x1, x2 = xmax, xmin

                if first_line:
                    commands.append(
                        Path.Command(
                            "G0",
                            {"X": x1, "Y": y, "Z": pass_z}
                        )
                    )
                    first_line = False
                else:
                    if not zigzag:
                        commands.append(Path.Command("G0", {"Z": safe_z}))
                    commands.append(Path.Command("G0", {"X": x1, "Y": y}))
                    if not zigzag:
                        commands.append(Path.Command("G0", {"Z": pass_z}))

                ocl_path = ocl.Path()
                ocl_path.append(
                    ocl.Line(
                        ocl.Point(x1, y, pass_z),
                        ocl.Point(x2, y, pass_z)
                    )
                )

                pdc = ocl.PathDropCutter()
                pdc.setSTL(surface)
                pdc.setCutter(cutter)
                pdc.setZ(pass_z)
                pdc.setSampling(sampling)
                pdc.setPath(ocl_path)
                pdc.run()

                cl_points = pdc.getCLPoints()

                points = [
                    FreeCAD.Vector(p.x, p.y, p.z)
                    for p in cl_points
                ]

                points = remove_collinear(points)

                for p in points:
                    # OCL gives the cutter-location Z required to follow the
                    # STL. Raise that complete roughing path by the requested
                    # Z allowance, so EVERY pass leaves the same material for
                    # finishing. The pass plane is also enforced so a pass
                    # cannot become deeper than its Step Down target.
                    cut_z = max(p.z + allowance_z, pass_z)
                    commands.append(
                        Path.Command(
                            "G1",
                            {"X": p.x, "Y": p.y, "Z": cut_z}
                        )
                    )

                reverse = not reverse

            # End of this roughing pass: retract to Job safe height
            # and return to the raster starting point before the next pass.
            if pass_index < total_passes - 1:
                commands.append(Path.Command("G0", {"Z": safe_z}))
                commands.append(
                    Path.Command(
                        "G0",
                        {"X": xmin, "Y": fixed_values[0]}
                    )
                )

    else:
        fixed_values = []
        x = xmin

        while x <= xmax + 1e-9:
            fixed_values.append(x)
            x += stepover

        if fixed_values[-1] < xmax - 1e-9:
            fixed_values.append(xmax)

        commands.append(
            Path.Command(
                "G0",
                {"X": fixed_values[0], "Y": ymin}
            )
        )

        total_lines = len(fixed_values)

        for pass_index, pass_z in enumerate(passes):
            first_line = True
            reverse = False

            for line_index, x in enumerate(fixed_values):
                progress_value = (
                    (pass_index * total_lines + line_index)
                    * 100.0
                    / max(1, total_passes * total_lines)
                )
                update_progress(
                    progress_value,
                    "Calculating... Pass %d/%d - Line %d/%d"
                    % (
                        pass_index + 1,
                        total_passes,
                        line_index + 1,
                        total_lines,
                    )
                )
                y1, y2 = ymin, ymax

                if zigzag and reverse:
                    y1, y2 = ymax, ymin

                if first_line:
                    commands.append(
                        Path.Command(
                            "G0",
                            {"X": x, "Y": y1, "Z": pass_z}
                        )
                    )
                    first_line = False
                else:
                    if not zigzag:
                        commands.append(Path.Command("G0", {"Z": safe_z}))
                    commands.append(Path.Command("G0", {"X": x, "Y": y1}))
                    if not zigzag:
                        commands.append(Path.Command("G0", {"Z": pass_z}))

                ocl_path = ocl.Path()
                ocl_path.append(
                    ocl.Line(
                        ocl.Point(x, y1, pass_z),
                        ocl.Point(x, y2, pass_z)
                    )
                )

                pdc = ocl.PathDropCutter()
                pdc.setSTL(surface)
                pdc.setCutter(cutter)
                pdc.setZ(pass_z)
                pdc.setSampling(sampling)
                pdc.setPath(ocl_path)
                pdc.run()

                cl_points = pdc.getCLPoints()

                points = [
                    FreeCAD.Vector(p.x, p.y, p.z)
                    for p in cl_points
                ]

                points = remove_collinear(points)

                for p in points:
                    # OCL gives the cutter-location Z required to follow the
                    # STL. Raise that complete roughing path by the requested
                    # Z allowance, so EVERY pass leaves the same material for
                    # finishing. The pass plane is also enforced so a pass
                    # cannot become deeper than its Step Down target.
                    cut_z = max(p.z + allowance_z, pass_z)
                    commands.append(
                        Path.Command(
                            "G1",
                            {"X": p.x, "Y": p.y, "Z": cut_z}
                        )
                    )

                reverse = not reverse

            # End of this roughing pass: retract to Job safe height
            # and return to the raster starting point before the next pass.
            if pass_index < total_passes - 1:
                commands.append(Path.Command("G0", {"Z": safe_z}))
                commands.append(
                    Path.Command(
                        "G0",
                        {"X": fixed_values[0], "Y": ymin}
                    )
                )

    commands.append(Path.Command("G0", {"Z": safe_z}))

    # Apply the Job Tool Controller feed/rapid rates to the COMPLETE path.
    # FreeCAD distinguishes G0 rapid moves from G1 cutting moves:
    #   G0 horizontal -> HorizRapid
    #   G0 vertical   -> VertRapid
    #   G1 horizontal -> HorizFeed
    #   G1 vertical   -> VertFeed
    # This is required so Cycle Time estimates Safe Height retracts and
    # positioning moves with the rapid rates, not the cutting feed.
    try:
        FeedRate.setFeedRate(commands, tool_controller)
    except Exception as e:
        FreeCAD.Console.PrintError(
            "Feed/rapid rate assignment failed: %s\\n" % str(e)
        )

    update_progress(100, "Calculation complete")
    return commands


# ---------------------------------------------------------------------------
# MAIN
# ---------------------------------------------------------------------------

doc = FreeCAD.ActiveDocument

if doc is None:
    QtWidgets.QMessageBox.critical(
        None,
        "STL 2.5D Engraving",
        "No active FreeCAD document."
    )
    raise RuntimeError("No active document")

mesh_obj = get_selected_mesh()

if mesh_obj is None:
    raise RuntimeError("No valid STL selected")

job = find_job(doc)

if job is None:
    raise RuntimeError("No valid CAM Job")

tool_controllers = get_tool_controllers(job)

if not tool_controllers:
    QtWidgets.QMessageBox.critical(
        None,
        "STL 2.5D Engraving",
        "No Tool Controller was found in the Job."
    )
    raise RuntimeError("No Tool Controller")

dlg = EngravingDialog(
    job,
    mesh_obj
)

if dlg.exec() != QtWidgets.QDialog.Accepted:
    raise RuntimeError("Operation cancelled")

params = dlg.values()
params["mesh_obj"] = mesh_obj

# Tool Controller handling:
# - Roughing: reuse the first Tool Controller from the Job, with no extra dialog.
# - Finishing: ask once, in French, before calculation.
#   This avoids the previous English dialog and avoids opening a second CAM panel.
if params["mode"] == "finishing":
    tool_labels = [tc.Label for tc in tool_controllers]
    selected_label, ok = QtWidgets.QInputDialog.getItem(
        None,
        "Sélection de l'outil",
        "Contrôleur d'outil :",
        tool_labels,
        0,
        False
    )
    if not ok:
        raise RuntimeError("Opération annulée")

    tool_controller = None
    for tc in tool_controllers:
        if tc.Label == selected_label:
            tool_controller = tc
            break

    if tool_controller is None:
        raise RuntimeError("Contrôleur d'outil introuvable")
else:
    tool_controller = tool_controllers[0]

try:
    FreeCAD.Console.PrintMessage(
        "\n--- STL 2.5D Engraving V1 ---\n"
    )

    FreeCAD.Console.PrintMessage(
        "Source: %s\n" % mesh_obj.Label
    )

    FreeCAD.Console.PrintMessage(
        "Tool: %s\n" % tool_controller.Label
    )

    op = create_operation(
        job,
        params
    )

    op.ToolController = tool_controller

    progress = QtWidgets.QProgressDialog(
        "Preparing calculation...",
        "Cancel",
        0,
        100
    )
    progress.setWindowTitle("STL 2.5D Engraving")
    progress.setWindowModality(QtCore.Qt.WindowModal)
    progress.setMinimumDuration(0)
    progress.setAutoClose(False)
    progress.setAutoReset(False)
    progress.setValue(0)
    progress.show()
    QtWidgets.QApplication.processEvents()

    try:
        commands = generate_toolpath(
            mesh_obj,
            tool_controller,
            params,
            job,
            progress
        )
    finally:
        progress.close()

    op.Path = Path.Path(commands)
    op.touch()

    doc.recompute()

    # Show the new operation.
    # No CAM task panel is opened here. The Tool Controller was deliberately
    # handled exactly once above: automatically for Roughing and with one
    # localized French selection dialog for Finishing.
    if hasattr(op, "ViewObject"):
        op.ViewObject.Visibility = True

    FreeCAD.Console.PrintMessage(
        "STL 2.5D Engraving operation created.\n"
    )
    FreeCAD.Console.PrintMessage(
        "Commands: %d\n" % len(commands)
    )
    FreeCAD.Console.PrintMessage(
        "--- Done ---\n"
    )

except Exception as e:
    try:
        if "op" in locals() and op:
            doc.removeObject(op.Name)
            doc.recompute()
    except Exception:
        pass

    FreeCAD.Console.PrintError(
        "STL 2.5D Engraving failed: %s\n" % str(e)
    )

    QtWidgets.QMessageBox.critical(
        None,
        "STL 2.5D Engraving",
        "The operation could not be generated.\n\n"
        + str(e)
    )
