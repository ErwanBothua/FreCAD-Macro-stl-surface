# -*- coding: utf-8 -*-
"""
FreeCAD CAM Macro - STL Surface V2

V2 development version.

Design principle:
    Reuse FreeCAD CAM's own strategy and surface-generation code as much as
    possible. Do not create a second CAM strategy engine.

Preferred path:
    FreeCAD surface_pattern -> XY scan lines -> FreeCAD surface_dropcutter/OCL
    -> FreeCAD Path -> existing Job.

Compatibility:
    - Newer FreeCAD versions: use Path.Base.Generator.surface_pattern and
      surface_dropcutter.
    - Older versions: fall back to Path.Op.SurfaceSupport.PathGeometryGenerator.

V1 remains untouched.
"""

import math

import FreeCAD
import FreeCADGui
import Path
import Path.Op.Custom as custom
import Path.Op.Gui.Base as GuiBase
from Path.Op.Gui.Base import CommandResources, TaskPanelPage
from Path.Base import FeedRate
import PathScripts.PathUtils as PathUtils
import Path.Op.SurfaceSupport as PathSurfaceSupport
import Path.Base.SetupSheet as PathSetupSheet
try:
    import Path.Op.Surface as PathSurface
except Exception:
    PathSurface = None
from PySide6 import QtWidgets, QtCore
from opencamlib import ocl

# V2 intentionally builds on FreeCAD CAM APIs instead of replacing them.
# The STL/Mesh -> OCL surface conversion is the only geometry-specific bridge.


# ---------------------------------------------------------------------------
# FreeCAD CAM imports
# ---------------------------------------------------------------------------

try:
    from Path.Base.Generator import surface_pattern
except Exception:
    surface_pattern = None

try:
    from Path.Base.Generator import surface_dropcutter
except Exception:
    surface_dropcutter = None

try:
    from Path.Op.SurfaceSupport import PathGeometryGenerator
except Exception:
    PathGeometryGenerator = None


# ---------------------------------------------------------------------------
# Helpers
# ---------------------------------------------------------------------------

def get_selected_mesh():
    sel = FreeCADGui.Selection.getSelection()

    if len(sel) != 1:
        QtWidgets.QMessageBox.critical(
            None,
            "STL Surface V2",
            "Select exactly ONE STL/Mesh object before starting the macro.",
        )
        return None

    obj = sel[0]

    if not obj.TypeId.startswith("Mesh"):
        QtWidgets.QMessageBox.critical(
            None,
            "STL Surface V2",
            "The selected object must be a Mesh/STL object.",
        )
        return None

    return obj


def find_jobs(doc):
    """
    Return every CAM Job in the active document.

    V2 deliberately does not assume that a Job is named "Job". FreeCAD
    documents may contain several Jobs, and users commonly rename their
    Job labels (for example Tile001, Tile002, ...).
    """
    jobs = []

    for obj in doc.Objects:
        try:
            if obj.TypeId.startswith("Path::Job"):
                jobs.append(obj)
                continue

            # Compatibility with FreeCAD variants where the concrete TypeId
            # is not exposed exactly as Path::Job.
            if hasattr(obj, "Tools") and hasattr(obj, "Model"):
                if obj.TypeId.startswith("Path"):
                    jobs.append(obj)
        except Exception:
            pass

    # Remove accidental duplicates while preserving document order.
    unique = []
    seen = set()

    for job in jobs:
        key = getattr(job, "Name", None)
        if key and key not in seen:
            seen.add(key)
            unique.append(job)

    return unique


def get_job_label(job):
    return getattr(job, "Label", getattr(job, "Name", "Job"))


def _native_surface_height(job, property_name, fallback):
    """Read a native CAM Job height when available, without requiring it."""
    try:
        value = getattr(job, property_name)
        if hasattr(value, "Value"):
            return float(value.Value)
        return float(value)
    except Exception:
        return float(fallback)


def _add_native_surface_properties(op, add_prop):
    """
    Mirror the important FreeCAD Surface operation property names.

    The STL operation remains a Custom operation because a Mesh/STL is not a
    normal Part::Feature face source for ObjectSurface.  Keeping the native
    Surface property vocabulary here is intentional: it makes the operation
    much easier to migrate into Path/Op when FreeCAD gains a native Mesh/STL
    surface source.
    """
    add_prop("App::PropertyEnumeration", "CutPattern", "Surface")
    add_prop("App::PropertyEnumeration", "CutMode", "Surface")
    add_prop("App::PropertyEnumeration", "LayerMode", "Depth")
    add_prop("App::PropertyAngle", "CutPatternAngle", "Surface")
    add_prop("App::PropertyBool", "CutPatternReversed", "Surface")
    add_prop("App::PropertyFloat", "StepOver", "Surface")
    add_prop("App::PropertyDistance", "SampleInterval", "Surface")
    add_prop("App::PropertyDistance", "StartDepth", "Depth")
    add_prop("App::PropertyDistance", "FinalDepth", "Depth")
    add_prop("App::PropertyDistance", "DepthOffset", "Depth")
    add_prop("App::PropertyDistance", "SafeHeight", "Depth")
    add_prop("App::PropertyDistance", "ClearanceHeight", "Depth")
    add_prop("App::PropertyBool", "CircularUseG2G3", "Optimization")

    try:
        op.CutPattern = [
            "Line", "Zigzag", "Circular",
            "CircularZigZag", "Offset", "Spiral"
        ]
        op.CutMode = ["Climb", "Conventional"]
        op.LayerMode = ["Single-pass", "Multi-pass"]
    except Exception:
        pass


def _set_native_surface_values(op, params, top_z):
    """Populate native Surface-compatible properties from V2 parameters."""
    pattern = params["strategy"]
    if pattern == "Circular Zigzag":
        pattern = "CircularZigZag"

    op.CutPattern = pattern
    op.CutMode = params.get("cut_mode", "Climb")
    op.LayerMode = params.get("layer_mode", "Multi-pass")
    op.CutPatternAngle = 90.0 if params["direction"] == "Y" else 0.0
    op.CutPatternReversed = bool(params.get("cut_pattern_reversed", False))
    op.StepOver = params["stepover_percent"]
    op.SampleInterval = params["sampling"]
    op.StartDepth = params.get("start_depth", top_z)
    op.FinalDepth = params.get("final_depth", top_z - params["depth"])
    op.DepthOffset = params.get("depth_offset", 0.0)
    op.SafeHeight = params.get("safe_height", top_z)
    op.ClearanceHeight = params.get("clearance_height", top_z)
    op.CircularUseG2G3 = bool(params.get("circular_use_g2g3", False))


def select_job(doc, mesh_obj):
    """
    Select the Job used by this operation.

    If there is only one Job, use it automatically.
    If several Jobs exist, show a selection dialog.
    """
    jobs = find_jobs(doc)

    if not jobs:
        QtWidgets.QMessageBox.critical(
            None,
            "STL Surface V2",
            "No CAM Job was found in the active document.",
        )
        return None

    if len(jobs) == 1:
        return jobs[0]

    labels = [
        get_job_label(job)
        for job in jobs
    ]

    selected_label, ok = QtWidgets.QInputDialog.getItem(
        None,
        "Sélection du Job",
        "Job CAM à utiliser :",
        labels,
        0,
        False,
    )

    if not ok:
        return None

    return jobs[labels.index(selected_label)]


def get_tool_controllers(job):
    result = []

    try:
        if job and job.Tools and job.Tools.Group:
            result.extend(job.Tools.Group)
    except Exception as exc:
        FreeCAD.Console.PrintError(
            "STL Surface V2: cannot read Job tools: %s\\n" % exc
        )

    return result


class _SurfaceSupportOperationShim:
    """
    Minimal adapter used only to call FreeCAD's own SurfaceSupport helpers.

    The machining algorithms stay in FreeCAD. The shim only supplies the
    properties that SurfaceSupport needs because our STL source is a Mesh
    rather than the normal Part/Job Base geometry of ObjectSurface.
    """
    def __init__(self, tool_controller, linear_deflection=0.001,
                 angular_deflection=0.523599):
        self.ToolController = tool_controller
        self.LinearDeflection = FreeCAD.Units.Quantity(
            "%s mm" % float(linear_deflection)
        )
        self.AngularDeflection = FreeCAD.Units.Quantity(
            "%s rad" % float(angular_deflection)
        )


def make_ocl_surface(mesh_obj, linear_deflection=0.001):
    """Use FreeCAD SurfaceSupport native Mesh -> OCL conversion.

    FreeCAD 1.1.x exposes Mesh.Facets as a Python list, while the
    SurfaceSupport code used by V2 expects the older attribute-style
    model.Mesh.Facets.Points interface. This adapter supports both
    representations without duplicating the STL/OCL conversion itself.
    """
    class _NativeFacetAdapter:
        def __init__(self, facet):
            self.Points = tuple(facet.Points)
            self.PointIndices = tuple(getattr(facet, "PointIndices", ()))

        def __iter__(self):
            return iter(self.Points)

    class _NativeFacetsAdapter:
        def __init__(self, mesh):
            self.Facets = [_NativeFacetAdapter(facet) for facet in mesh.Facets]
            self.Points = [facet.Points for facet in self.Facets]

        def __iter__(self):
            return iter(self.Facets)

    class _NativeMeshAdapter:
        def __init__(self, mesh):
            self.Facets = _NativeFacetsAdapter(mesh)
            self.Points = list(getattr(mesh, "Points", ()))

    class _NativeMeshModelAdapter:
        def __init__(self, mesh_obj):
            self.Mesh = _NativeMeshAdapter(mesh_obj.Mesh)

    shim = _SurfaceSupportOperationShim(
        None,
        linear_deflection=linear_deflection,
    )

    model_adapter = _NativeMeshModelAdapter(mesh_obj)

    return PathSurfaceSupport._makeSTL(
        model_adapter,
        shim,
        ocl,
        model_type="M",
    )
def make_ocl_cutter(tool_controller):
    """Use FreeCAD's native ToolBit -> OCL cutter conversion."""
    shim = _SurfaceSupportOperationShim(tool_controller)
    ocl_tool = PathSurfaceSupport.OCL_Tool(
        ocl,
        shim,
    )
    cutter = ocl_tool.getOclTool()
    if cutter is None:
        raise RuntimeError("FreeCAD SurfaceSupport could not create an OCL cutter.")
    return cutter


def make_planar_bbox(mesh_obj, margin=0.0, allowance_xy=0.0):
    """
    Create the planar boundary used by FreeCAD's strategy engine.

    Allowance XY shrinks the machining region.
    Margin expands it.
    The STL itself is still used by OCL for the Z calculation.
    """
    import Part

    bb = mesh_obj.Mesh.BoundBox

    xmin = bb.XMin - margin + allowance_xy
    xmax = bb.XMax + margin - allowance_xy
    ymin = bb.YMin - margin + allowance_xy
    ymax = bb.YMax + margin - allowance_xy

    if xmax <= xmin or ymax <= ymin:
        raise RuntimeError(
            "Margin/Allowance XY leaves no usable machining area."
        )

    p1 = FreeCAD.Vector(xmin, ymin, 0.0)
    p2 = FreeCAD.Vector(xmax, ymin, 0.0)
    p3 = FreeCAD.Vector(xmax, ymax, 0.0)
    p4 = FreeCAD.Vector(xmin, ymax, 0.0)

    edges = [
        Part.makeLine(p1, p2),
        Part.makeLine(p2, p3),
        Part.makeLine(p3, p4),
        Part.makeLine(p4, p1),
    ]

    return Part.Face(Part.Wire(edges))


# ---------------------------------------------------------------------------
# Legacy FreeCAD SurfaceSupport compatibility
# ---------------------------------------------------------------------------

class LegacyStrategyAdapter:
    """
    Small adapter for FreeCAD's older PathGeometryGenerator.

    The legacy generator expects StepOver as a percentage of tool diameter
    and SampleInterval as a FreeCAD Quantity.
    """

    def __init__(
        self,
        tool_controller,
        step_over_percent,
        sampling,
        direction,
    ):
        self.ToolController = tool_controller
        self.StepOver = float(step_over_percent)

        self.SampleInterval = FreeCAD.Units.Quantity(
            "%s mm" % float(sampling)
        )

        self.CutMode = "Climb"
        self.CutPatternReversed = False

        self.CutPatternAngle = 0.0
        if direction == "Y":
            self.CutPatternAngle = 90.0

        self.PatternCenterAt = "CenterOfBoundBox"
        self.PatternCenterCustom = FreeCAD.Vector(0.0, 0.0, 0.0)


def legacy_geometry_to_polylines(geometry, sampling):
    """
    Convert legacy FreeCAD planar geometry into independent XY polylines.

    Each edge is kept as a separate polyline so disconnected Offset geometry
    does not become an artificial cutting move.
    """
    polylines = []

    for edge in getattr(geometry, "Edges", []):
        try:
            pts = edge.discretize(
                Distance=max(float(sampling), 0.001)
            )
        except Exception:
            pts = [v.Point for v in edge.Vertexes]

        if len(pts) < 2:
            continue

        line = [
            (float(p.x), float(p.y), 0.0)
            for p in pts
        ]

        polylines.append(line)

    return polylines


# ---------------------------------------------------------------------------
# FreeCAD strategy engine
# ---------------------------------------------------------------------------

def generate_strategy_polylines(
    mesh_obj,
    tool_controller,
    params,
    progress_callback=None,
):
    """
    Ask FreeCAD itself to generate the XY strategy.

    New FreeCAD:
        surface_pattern.fast_generate_pattern()
        surface_pattern.generate_offset_scan_lines()

    Legacy FreeCAD:
        PathGeometryGenerator
    """

    def progress(value, text):
        if progress_callback:
            progress_callback(value, text)

    strategy = params["strategy"]

    planar_shape = make_planar_bbox(
        mesh_obj,
        params["margin"],
        params["allowance_xy"],
    )

    bb = mesh_obj.Mesh.BoundBox

    tool_diameter = float(tool_controller.Tool.Diameter.Value)

    # FreeCAD Surface uses StepOver as a percentage of tool diameter.
    stepover_mm = (
        tool_diameter * params["stepover_percent"] / 100.0
    )

    if stepover_mm <= 0.0:
        raise RuntimeError("Step Over must produce a positive stepover.")

    sampling = max(float(params["sampling"]), 0.001)

    # ------------------------------------------------------------------
    # Modern FreeCAD strategy engine
    # ------------------------------------------------------------------
    if surface_pattern is not None:
        progress(
            8,
            "FreeCAD: generating %s strategy..." % strategy,
        )

        bbox = surface_pattern.BBox.from_bbox(bb)

        # Apply the same Margin / Allowance XY region used by this macro.
        bbox = surface_pattern.BBox(
            bb.XMin - params["margin"] + params["allowance_xy"],
            bb.XMax + params["margin"] - params["allowance_xy"],
            bb.YMin - params["margin"] + params["allowance_xy"],
            bb.YMax + params["margin"] - params["allowance_xy"],
        )

        center = bbox.center

        angle = 0.0
        if params["direction"] == "Y":
            angle = 90.0

        climb = True
        reversed_pattern = False
        is_zigzag = strategy in ("Zigzag", "Circular Zigzag")

        if strategy == "Offset":
            polylines = surface_pattern.generate_offset_scan_lines(
                planar_shape,
                stepover_mm,
                tool_diameter,
                sampling,
                reversed_pattern=reversed_pattern,
                climb=climb,
            )
        else:
            pattern_name = strategy

            # FreeCAD uses CircularZigZag internally.
            if pattern_name == "Circular Zigzag":
                pattern_name = "CircularZigZag"

            polylines = surface_pattern.fast_generate_pattern(
                pattern_name,
                bbox,
                center,
                stepover_mm,
                sampling,
                angle,
                is_zigzag,
                reversed_pattern,
                climb,
                planar_shape,
            )

        if not polylines:
            raise RuntimeError(
                "FreeCAD generated no toolpath for strategy %s."
                % strategy
            )

        progress(
            20,
            "FreeCAD: %d strategy paths generated." % len(polylines),
        )

        return polylines

    # ------------------------------------------------------------------
    # Legacy FreeCAD strategy engine
    # ------------------------------------------------------------------
    if PathGeometryGenerator is None:
        raise RuntimeError(
            "No FreeCAD Surface strategy generator is available."
        )

    progress(
        8,
        "FreeCAD legacy SurfaceSupport: generating %s..."
        % strategy,
    )

    legacy_name = {
        "Circular Zigzag": "CircularZigZag",
    }.get(strategy, strategy)

    adapter = LegacyStrategyAdapter(
        tool_controller,
        params["stepover_percent"],
        sampling,
        params["direction"],
    )

    generator = PathGeometryGenerator(
        adapter,
        planar_shape,
        legacy_name,
    )

    geometry = generator.generatePathGeometry()

    if not geometry:
        raise RuntimeError(
            "FreeCAD generated no toolpath for strategy %s."
            % strategy
        )

    polylines = legacy_geometry_to_polylines(
        geometry,
        sampling,
    )

    if not polylines:
        raise RuntimeError(
            "FreeCAD generated geometry, but no usable paths were extracted."
        )

    progress(
        20,
        "FreeCAD legacy: %d strategy paths generated."
        % len(polylines),
    )

    return polylines


# ---------------------------------------------------------------------------
# Native FreeCAD Surface algorithm adapter
# ---------------------------------------------------------------------------

class NativeSurfaceAlgorithmAdapter:
    """
    Reuse FreeCAD 1.1.x ObjectSurface algorithms directly.

    This object is only a bridge because ObjectSurface normally receives its
    geometry through a standard CAM Base property. V2 supplies the STL/OCL
    data itself, then delegates depth processing, linear-path processing and
    step-over transitions to FreeCAD's own implementation.
    """
    def __init__(self, tool_controller, cutter, params):
        if PathSurface is None:
            raise RuntimeError("FreeCAD Surface operation is unavailable.")

        self.impl = PathSurface.ObjectSurface.__new__(PathSurface.ObjectSurface)
        self.impl.cutter = cutter
        self.impl.toolDiam = float(tool_controller.Tool.Diameter.Value)

        # Native FreeCAD Surface builds Path.Command dictionaries from these
        # feed values. ToolController properties may be Quantity objects;
        # Path.Command requires plain numeric values.
        def _numeric(value, default=0.0):
            try:
                if hasattr(value, "Value"):
                    return float(value.Value)
                return float(value)
            except Exception:
                return float(default)

        self.impl.horizFeed = _numeric(getattr(tool_controller, "HorizFeed", 0.0))
        self.impl.horizRapid = _numeric(getattr(tool_controller, "HorizRapid", 0.0))
        self.impl.vertRapid = _numeric(getattr(tool_controller, "VertRapid", 0.0))
        self.impl.vertFeed = _numeric(getattr(tool_controller, "VertFeed", 0.0))
        self.impl.CutClimb = params.get("cut_mode", "Climb") == "Climb"
        self.impl.preOLP = bool(params.get("optimize_linear_paths", True))
        self.impl.tmpCOM = FreeCAD.Vector(0.0, 0.0, 0.0)

    def singlepass(self, op, points):
        return self.impl._planarSinglepassProcess(op, points)

    def multipass_preprocess(self, op, points, prev_depth, layer_depth):
        return self.impl._planarMultipassPreProcess(
            op, points, prev_depth, layer_depth
        )

    def multipass_process(self, op, points, max_z):
        return self.impl._planarMultipassProcess(op, points, max_z)

    def transition(self, op, p1, p2, safe_pdc, tolerance):
        return self.impl._stepTransitionCmds(
            op, p1, p2, safe_pdc, tolerance
        )

# ---------------------------------------------------------------------------
# OCL projection
# ---------------------------------------------------------------------------

def project_with_freecad_surface_generator(
    surface,
    cutter,
    polylines,
    min_z,
    sampling,
    mode,
):
    """
    Reuse FreeCAD's OCL wrapper whenever available.

    BatchDropCutter is preferred for dense modern strategies.
    PathDropCutter is retained for path-oriented strategies.
    AdaptivePathDropCutter is available for finishing.
    """

    if surface_dropcutter is None:
        return None

    if mode == "Finishing" and hasattr(
        surface_dropcutter,
        "adaptive_path_dropcutter",
    ):
        return surface_dropcutter.adaptive_path_dropcutter(
            surface,
            cutter,
            polylines,
            min_z,
            sampling,
            max(sampling / 10.0, 0.001),
        )

    if hasattr(surface_dropcutter, "path_dropcutter"):
        return surface_dropcutter.path_dropcutter(
            surface,
            cutter,
            polylines,
            min_z,
            sampling,
        )

    return None


def project_polyline_with_ocl(
    surface,
    cutter,
    polyline,
    min_z,
    sampling,
    mode,
):
    """
    Project one FreeCAD strategy polyline with OCL.

    Keeping the projection per source polyline is intentional in V2:
    it preserves the natural breaks between scan lines/offset loops, which
    lets the rest-machining optimizer insert rapids instead of accidentally
    connecting two disconnected cutting regions.
    """

    if len(polyline) < 2:
        return []

    projected = project_with_freecad_surface_generator(
        surface,
        cutter,
        [polyline],
        min_z,
        sampling,
        mode,
    )

    if projected is not None:
        return [
            FreeCAD.Vector(
                float(p[0]),
                float(p[1]),
                float(p[2]),
            )
            for p in projected
        ]

    ocl_path = ocl.Path()

    for p1, p2 in zip(polyline[:-1], polyline[1:]):
        ocl_path.append(
            ocl.Line(
                ocl.Point(p1[0], p1[1], min_z),
                ocl.Point(p2[0], p2[1], min_z),
            )
        )

    pdc = ocl.PathDropCutter()
    pdc.setSTL(surface)
    pdc.setCutter(cutter)
    pdc.setZ(min_z)
    pdc.setSampling(sampling)
    pdc.setPath(ocl_path)
    pdc.run()

    return [
        FreeCAD.Vector(
            float(cl.x),
            float(cl.y),
            float(cl.z),
        )
        for cl in pdc.getCLPoints()
    ]




# ---------------------------------------------------------------------------
# Custom operation
# ---------------------------------------------------------------------------

def create_operation(job, mesh_obj, tool_controller, params):
    op = custom.Create(
        "STL_Surface_V2",
        parentJob=job,
    )

    if not hasattr(op, "Proxy") or not isinstance(
        op.Proxy,
        custom.ObjectCustom,
    ):
        custom.ObjectCustom(op)

    if FreeCAD.GuiUp:
        resources = CommandResources(
            name="STL Surface V2",
            objFactory=custom.Create,
            opPageClass=TaskPanelPage,
            pixmap="CAM_Custom",
            menuText="STL Surface V2",
            accelKey="",
            toolTip="FreeCAD CAM strategies + OpenCAMLib",
        )

        op.ViewObject.Proxy = GuiBase.ViewProvider(
            op.ViewObject,
            resources,
        )

    def add_prop(prop_type, name, group, desc=""):
        if not hasattr(op, name):
            op.addProperty(
                prop_type,
                name,
                group,
                desc,
            )

    add_prop(
        "App::PropertyBool",
        "IsCustomOp",
        "Path",
    )

    # Keep the native Surface property vocabulary alongside the STL-specific
    # properties. This is the key compatibility seam for future integration.
    _add_native_surface_properties(op, add_prop)
    add_prop(
        "App::PropertyLink",
        "STLSource",
        "Geometry",
    )
    add_prop(
        "App::PropertyLink",
        "ToolController",
        "Path",
    )
    add_prop(
        "App::PropertyString",
        "Strategy",
        "Strategy",
    )
    add_prop(
        "App::PropertyString",
        "Mode",
        "Strategy",
    )
    add_prop(
        "App::PropertyString",
        "Direction",
        "Strategy",
    )
    add_prop(
        "App::PropertyDistance",
        "DepthLimit",
        "Parameters",
    )
    add_prop(
        "App::PropertyFloat",
        "StepOverPercent",
        "Parameters",
    )
    add_prop(
        "App::PropertyDistance",
        "StepDown",
        "Parameters",
    )
    add_prop(
        "App::PropertyDistance",
        "AllowanceXY",
        "Parameters",
    )
    add_prop(
        "App::PropertyDistance",
        "AllowanceZ",
        "Parameters",
    )
    add_prop(
        "App::PropertyDistance",
        "Margin",
        "Parameters",
    )
    add_prop(
        "App::PropertyDistance",
        "Sampling",
        "Parameters",
    )
    add_prop(
        "App::PropertyBool",
        "OptimizeLinearPaths",
        "Optimization",
    )
    add_prop(
        "App::PropertyBool",
        "OptimizeStepOverTransitions",
        "Optimization",
    )
    add_prop(
        "App::PropertyDistance",
        "GapThreshold",
        "Optimization",
    )
    add_prop(
        "App::PropertyDistance",
        "LinearDeflection",
        "Optimization",
    )
    add_prop(
        "App::PropertyString",
        "OptimizationBackend",
        "Optimization",
    )

    # The generated Path is already the final CAM result. Do not leave
    # ObjectCustom as the live execution proxy: its normal execute() rebuilds
    # Path from the Custom G-code field and would overwrite our generated path
    # during the next document recompute.
    op.IsCustomOp = True
    op.STLSource = mesh_obj
    op.ToolController = tool_controller
    op.Strategy = params["strategy"]
    op.Mode = params["mode"]
    op.Direction = params["direction"]
    op.DepthLimit = params["depth"]
    op.StepOverPercent = params["stepover_percent"]
    op.StepDown = params["stepdown"]
    op.AllowanceXY = params["allowance_xy"]
    op.AllowanceZ = params["allowance_z"]
    op.Margin = params["margin"]
    op.Sampling = params["sampling"]
    op.OptimizeLinearPaths = params["optimize_linear_paths"]
    op.OptimizeStepOverTransitions = params["optimize_stepover_transitions"]
    op.GapThreshold = params["gap_threshold"]
    op.LinearDeflection = params["linear_deflection"]
    _set_native_surface_values(op, params, params.get("top_z", 0.0))
    op.OptimizationBackend = (
        "FreeCAD SurfaceSupport + PathUtils + OCL; "
        "native Surface property compatibility layer"
    )

    return op


# ---------------------------------------------------------------------------
# Toolpath generation
# ---------------------------------------------------------------------------

def generate_toolpath(
    mesh_obj,
    tool_controller,
    params,
    job,
    progress=None,
):
    def update_progress(value, message):
        if progress is None:
            return

        progress.setValue(
            max(0, min(100, int(value)))
        )
        progress.setLabelText(message)
        QtWidgets.QApplication.processEvents()

        if progress.wasCanceled():
            raise RuntimeError(
                "Calculation cancelled by user"
            )

    cutter = make_ocl_cutter(tool_controller)
    surface = make_ocl_surface(
        mesh_obj,
        float(params.get("linear_deflection", 0.001)),
    )

    update_progress(
        2,
        "Preparing STL surface...",
    )

    polylines = generate_strategy_polylines(
        mesh_obj,
        tool_controller,
        params,
        update_progress,
    )

    bb = mesh_obj.Mesh.BoundBox
    top_z = bb.ZMax

    depth = float(params["depth"])
    step_down = max(
        float(params["stepdown"]),
        0.001,
    )

    # V2 keeps the V1 roughing model for now. It will be validated against
    # real machines before changing allowance/depth semantics.
    if params["mode"] == "Finishing":
        passes = [top_z - depth]
    else:
        pass_count = max(
            1,
            int(math.ceil(depth / step_down)),
        )
        passes = []

        for index in range(pass_count):
            pass_depth = min(
                depth,
                (index + 1) * step_down,
            )
            passes.append(
                top_z - pass_depth
            )

    # Native Surface semantics: retain the same depth vocabulary used by
    # FreeCAD. SafeHeight/StartDepth are currently resolved from the Job when
    # a usable native value exists; otherwise the proven V1/V2 top-Z fallback
    # is retained until this operation is fully delegated to ObjectSurface.
    params["top_z"] = top_z
    params["start_depth"] = top_z
    params["final_depth"] = top_z - depth
    params["depth_offset"] = float(params.get("depth_offset", 0.0))

    job_clearance = _native_surface_height(job, "ClearanceHeight", top_z)
    safe_z = max(top_z, job_clearance)
    params["safe_height"] = safe_z
    params["clearance_height"] = job_clearance

    commands = []

    native = NativeSurfaceAlgorithmAdapter(
        tool_controller,
        cutter,
        params,
    )

    # Build the same SCANDATA nesting expected by FreeCAD Surface.
    # Each FreeCAD-generated strategy polyline remains a separate step-over.
    scan_data = []
    for polyline in polylines:
        projected = project_polyline_with_ocl(
            surface,
            cutter,
            polyline,
            passes[-1],
            float(params["sampling"]),
            params["mode"],
        )
        if projected and len(projected) >= 2:
            scan_data.append([projected])

    if not scan_data:
        raise RuntimeError("No OCL scan data was generated.")

    # Native FreeCAD Surface expects an operation object exposing its normal
    # Surface properties. We keep the STL-specific Custom operation but feed
    # the native algorithm a property-compatible shim.
    surface_op = type("NativeSurfaceProperties", (), {})()
    surface_op.SafeHeight = FreeCAD.Units.Quantity("%s mm" % safe_z)
    surface_op.ClearanceHeight = FreeCAD.Units.Quantity("%s mm" % job_clearance)
    surface_op.StepDown = FreeCAD.Units.Quantity("%s mm" % step_down)
    surface_op.LinearDeflection = FreeCAD.Units.Quantity(
        "%s mm" % float(params["linear_deflection"])
    )
    surface_op.FinalDepth = FreeCAD.Units.Quantity(
        "%s mm" % (top_z - depth)
    )
    surface_op.OptimizeLinearPaths = bool(params["optimize_linear_paths"])
    surface_op.OptimizeStepOverTransitions = bool(params["optimize_stepover_transitions"])
    surface_op.CutPattern = "CircularZigZag" if params["strategy"] == "Circular Zigzag" else params["strategy"]
    surface_op.CircularUseG2G3 = bool(params.get("circular_use_g2g3", False))
    surface_op.ProfileEdges = "None"
    surface_op.HandleMultipleFeatures = "Collectively"

    # One OCL PDC is shared by all FreeCAD strategy segments, exactly as the
    # native planar Surface implementation does.
    pdc = ocl.PathDropCutter()
    pdc.setSTL(surface)
    pdc.setCutter(cutter)
    pdc.setZ(passes[-1])
    pdc.setSampling(float(params["sampling"]))

    # Use the native Surface transition algorithm. The current STL source is
    # itself the collision surface; a dedicated stock-safe STL can be wired in
    # later without changing the transition code path.
    safe_pdc = pdc

    tolerance = _native_surface_height(job, "GeometryTolerance", 0.001)
    depth_params = list(passes)

    if params["mode"] == "Finishing":
        previous_end = None
        for step in scan_data:
            for points in step:
                if (
                    previous_end is not None
                    and params.get("optimize_stepover_transitions", False)
                ):
                    commands.extend(
                        native.transition(
                            surface_op,
                            previous_end,
                            points[0],
                            safe_pdc,
                            tolerance,
                        )
                    )
                commands.extend(native.singlepass(surface_op, points))
                previous_end = points[-1]
    else:
        # Delegate layer-depth handling and hold-point logic to FreeCAD.
        prev_depth = depth_params[0]
        for layer_depth in depth_params:
            previous_end = None
            for step in scan_data:
                for points in step:
                    pts, max_z = native.multipass_preprocess(
                        surface_op,
                        list(points),
                        prev_depth,
                        layer_depth,
                    )
                    if pts:
                        if (
                            previous_end is not None
                            and params.get("optimize_stepover_transitions", False)
                        ):
                            commands.extend(
                                native.transition(
                                    surface_op,
                                    previous_end,
                                    pts[0],
                                    safe_pdc,
                                    tolerance,
                                )
                            )
                        commands.extend(
                            native.multipass_process(surface_op, pts, max_z)
                        )
                        previous_end = pts[-1]
            prev_depth = layer_depth


    commands.append(
        Path.Command(
            "G0",
            {"Z": safe_z},
        )
    )

    try:
        FeedRate.setFeedRate(
            commands,
            tool_controller,
        )
    except Exception as exc:
        FreeCAD.Console.PrintError(
            "STL Surface V2: FeedRate failed: %s\\n"
            % exc
        )

    update_progress(
        100,
        "STL Surface V2 complete.",
    )

    return commands


# ---------------------------------------------------------------------------
# Dialog
# ---------------------------------------------------------------------------

class SurfaceV2Dialog(QtWidgets.QDialog):
    def __init__(self, job, mesh_obj):
        super().__init__()

        self.setWindowTitle(
            "STL Surface V2"
        )
        self.setMinimumWidth(450)

        layout = QtWidgets.QFormLayout(self)

        self.source = QtWidgets.QLabel(
            mesh_obj.Label
        )
        self.job_label = QtWidgets.QLabel(
            job.Label
        )

        self.strategy = QtWidgets.QComboBox()
        self.strategy.addItems(
            [
                "Line",
                "Zigzag",
                "Circular",
                "Circular Zigzag",
                "Offset",
                "Spiral",
            ]
        )

        self.mode = QtWidgets.QComboBox()
        self.mode.addItems(
            [
                "Roughing",
                "Finishing",
            ]
        )

        # Match FreeCAD Surface: StepOver is percentage of tool diameter.
        self.step_over = QtWidgets.QDoubleSpinBox()
        self.step_over.setRange(
            0.1,
            100.0,
        )
        self.step_over.setValue(40.0)
        self.step_over.setDecimals(2)
        self.step_over.setSuffix(" %")

        self.step_down = QtWidgets.QDoubleSpinBox()
        self.step_down.setRange(
            0.001,
            10000.0,
        )
        self.step_down.setValue(1.0)
        self.step_down.setDecimals(3)
        self.step_down.setSuffix(" mm")

        self.depth = QtWidgets.QDoubleSpinBox()
        self.depth.setRange(
            0.001,
            10000.0,
        )
        self.depth.setValue(1.0)
        self.depth.setDecimals(3)
        self.depth.setSuffix(" mm")

        self.allowance_xy = QtWidgets.QDoubleSpinBox()
        self.allowance_xy.setRange(
            0.0,
            1000.0,
        )
        self.allowance_xy.setValue(0.0)
        self.allowance_xy.setDecimals(3)
        self.allowance_xy.setSuffix(" mm")

        self.allowance_z = QtWidgets.QDoubleSpinBox()
        self.allowance_z.setRange(
            0.0,
            1000.0,
        )
        self.allowance_z.setValue(0.0)
        self.allowance_z.setDecimals(3)
        self.allowance_z.setSuffix(" mm")

        self.margin = QtWidgets.QDoubleSpinBox()
        self.margin.setRange(
            0.0,
            1000.0,
        )
        self.margin.setValue(0.0)
        self.margin.setDecimals(3)
        self.margin.setSuffix(" mm")

        self.sampling = QtWidgets.QDoubleSpinBox()
        self.sampling.setRange(
            0.01,
            100.0,
        )
        self.sampling.setValue(1.0)
        self.sampling.setDecimals(3)
        self.sampling.setSuffix(" mm")

        self.direction = QtWidgets.QComboBox()
        self.direction.addItems(
            ["X", "Y"]
        )

        self.optimize_linear = QtWidgets.QCheckBox()
        self.optimize_linear.setChecked(True)

        self.optimize_transitions = QtWidgets.QCheckBox()
        self.optimize_transitions.setChecked(False)

        self.gap_threshold = QtWidgets.QDoubleSpinBox()
        self.gap_threshold.setRange(0.0, 100.0)
        self.gap_threshold.setValue(0.005)
        self.gap_threshold.setDecimals(4)
        self.gap_threshold.setSuffix(" mm")

        self.linear_deflection = QtWidgets.QDoubleSpinBox()
        self.linear_deflection.setRange(0.000001, 100.0)
        self.linear_deflection.setValue(0.001)
        self.linear_deflection.setDecimals(6)
        self.linear_deflection.setSuffix(" mm")

        layout.addRow(
            "STL:",
            self.source,
        )
        layout.addRow(
            "Job:",
            self.job_label,
        )
        layout.addRow(
            "Strategy:",
            self.strategy,
        )
        layout.addRow(
            "Mode:",
            self.mode,
        )
        layout.addRow(
            "Step Over:",
            self.step_over,
        )
        layout.addRow(
            "Step Down:",
            self.step_down,
        )
        layout.addRow(
            "Depth Limit:",
            self.depth,
        )
        layout.addRow(
            "Allowance XY:",
            self.allowance_xy,
        )
        layout.addRow(
            "Allowance Z:",
            self.allowance_z,
        )
        layout.addRow(
            "Margin:",
            self.margin,
        )
        layout.addRow(
            "OCL Sampling:",
            self.sampling,
        )
        layout.addRow(
            "Direction:",
            self.direction,
        )
        layout.addRow(
            "Optimize Linear Paths:",
            self.optimize_linear,
        )
        layout.addRow(
            "Optimize Step Over Transitions:",
            self.optimize_transitions,
        )
        layout.addRow(
            "Gap Threshold:",
            self.gap_threshold,
        )
        layout.addRow(
            "Linear Deflection:",
            self.linear_deflection,
        )

        buttons = QtWidgets.QDialogButtonBox(
            QtWidgets.QDialogButtonBox.Ok
            | QtWidgets.QDialogButtonBox.Cancel
        )

        buttons.accepted.connect(
            self.accept
        )
        buttons.rejected.connect(
            self.reject
        )

        layout.addRow(
            buttons
        )

        self.mode.currentTextChanged.connect(
            self.update_mode
        )

        self.update_mode(
            self.mode.currentText()
        )

    def update_mode(self, mode):
        finishing = mode == "Finishing"

        self.step_down.setEnabled(
            not finishing
        )
        self.allowance_xy.setEnabled(
            not finishing
        )
        self.allowance_z.setEnabled(
            not finishing
        )

        if finishing:
            self.step_down.setValue(
                self.depth.value()
            )
            self.allowance_xy.setValue(
                0.0
            )
            self.allowance_z.setValue(
                0.0
            )

    def values(self):
        return {
            "strategy": self.strategy.currentText(),
            "mode": self.mode.currentText(),
            "stepover_percent": self.step_over.value(),
            "stepdown": self.step_down.value(),
            "depth": self.depth.value(),
            "allowance_xy": self.allowance_xy.value(),
            "allowance_z": self.allowance_z.value(),
            "margin": self.margin.value(),
            "sampling": self.sampling.value(),
            "direction": self.direction.currentText(),
            # Native FreeCAD Surface vocabulary. The current V2 UI keeps these
            # fixed until the native task-panel integration is introduced.
            "cut_mode": "Climb",
            "cut_pattern_reversed": False,
            "layer_mode": "Multi-pass",
            "circular_use_g2g3": False,
            "optimize_linear_paths": self.optimize_linear.isChecked(),
            "optimize_stepover_transitions": self.optimize_transitions.isChecked(),
            "gap_threshold": self.gap_threshold.value(),
            "linear_deflection": self.linear_deflection.value(),
        }


# ---------------------------------------------------------------------------
# Main
# ---------------------------------------------------------------------------

# Register the operation with FreeCAD's SetupSheet system. This is
# intentionally only metadata registration; the actual toolpath remains the
# Path generated by V2.
try:
    PathSetupSheet.RegisterOperation(
        "STL_Surface_V2",
        custom.Create,
        custom.SetupProperties,
    )
except Exception:
    pass


def main():
    if not FreeCAD.GuiUp:
        raise RuntimeError(
            "STL Surface V2 requires the FreeCAD GUI."
        )

    doc = FreeCAD.ActiveDocument

    if doc is None:
        QtWidgets.QMessageBox.critical(
            None,
            "STL Surface V2",
            "No active FreeCAD document.",
        )
        return

    mesh_obj = get_selected_mesh()

    if mesh_obj is None:
        return

    job = select_job(doc, mesh_obj)

    if job is None:
        return

    dialog = SurfaceV2Dialog(
        job,
        mesh_obj,
    )

    if dialog.exec() != QtWidgets.QDialog.Accepted:
        return

    params = dialog.values()

    controllers = get_tool_controllers(job)

    if not controllers:
        QtWidgets.QMessageBox.critical(
            None,
            "STL Surface V2",
            "No Tool Controller was found in the Job.",
        )
        return

    labels = [
        tc.Label
        for tc in controllers
    ]

    selected_label, ok = QtWidgets.QInputDialog.getItem(
        None,
        "Sélection de l'outil",
        "Contrôleur d'outil :",
        labels,
        0,
        False,
    )

    if not ok:
        return

    tool_controller = controllers[
        labels.index(selected_label)
    ]

    progress = QtWidgets.QProgressDialog(
        "Preparing...",
        "Cancel",
        0,
        100,
    )

    progress.setWindowTitle(
        "STL Surface V2"
    )
    progress.setWindowModality(
        QtCore.Qt.WindowModal
    )
    progress.setMinimumDuration(
        0
    )
    progress.setValue(
        0
    )
    progress.show()

    QtWidgets.QApplication.processEvents()

    try:
        commands = generate_toolpath(
            mesh_obj,
            tool_controller,
            params,
            job,
            progress,
        )

        if not commands:
            raise RuntimeError(
                "No toolpath was generated."
            )

        op = create_operation(
            job,
            mesh_obj,
            tool_controller,
            params,
        )

        # Store the generated CAM path directly on the Job operation.
        # V2 generates the complete Path itself, so ObjectCustom must not
        # execute again and replace it with its empty Custom-Gcode Path.
        op.Path = Path.Path(commands)

        # Freeze this generated operation after path creation. The geometry
        # calculation is performed by V2 and delegated to FreeCAD/OCL above;
        # recomputing an ObjectCustom proxy would regenerate an empty path.
        op.Proxy = None

        doc.recompute()

        FreeCADGui.activeDocument().activeView().fitAll()

        FreeCAD.Console.PrintMessage(
            "STL Surface V2: operation '%s' created with strategy '%s'.\\n"
            % (
                op.Label,
                params["strategy"],
            )
        )

    except Exception as exc:
        FreeCAD.Console.PrintError(
            "STL Surface V2 ERROR: %s\\n"
            % exc
        )

        QtWidgets.QMessageBox.critical(
            None,
            "STL Surface V2",
            str(exc),
        )

    finally:
        progress.close()
        progress.deleteLater()


main()
